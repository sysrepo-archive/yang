module "sysrepo-lwaftr-loadtest" {

    namespace "urn:ietf:params:xml:ns:yang:sysrepo-lwaftr-loadtest" ;

    prefix "ie" ;

    organization "sysrepo" ;

    contact "support@freenetconf.org
    Editor:   Mislav Novakovic
               <mislav.novakovic@sartura.hr>";

    description "yang model for loadtester in snabb" ;

    revision "2016-06-09" {
        reference "https://github.com/freenetconf/yang-creator" ;
    }

    container "loadtest" {
        config "false";
        description
            "loadtest configuration parameters.";
        list "nic" {
            key "name";
            config "false";
            description
                "nic properties";
            leaf "name" {
                type "string";
                description
                  "name of the nic interface";
            }
            leaf "capture_file" {
                type "string";
                description
                  "name of the nic.";
            }
            leaf "pci_addr" {
                type "string";
                description
                  "pci address of the nic.";
            }
            leaf "tx_name" {
                type "string";
                description
                  "tx name";
            }
            leaf "rx_name" {
                type "string";
                description
                  "rx name";
            }
            leaf "tx_id" {
                type "string";
                description
                  "tx id";
            }
            leaf "rx_id" {
                type "string";
                description
                  "rx id";
            }
        }
    }
}
