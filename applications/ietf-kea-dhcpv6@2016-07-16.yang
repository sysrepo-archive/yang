module ietf-kea-dhcpv6 {
    namespace "urn:ietf:params:xml:ns:yang:ietf-kea-dhcpv6";
    prefix "dhcpv6";

    import ietf-inet-types { 
        prefix inet; 
        revision-date "2013-07-15"; 
    }
    import ietf-yang-types { 
        prefix yang; 
        revision-date "2013-07-15"; 
    }

    organization "ISC, DT, Sysrepo, Tsinghua";

    contact "lh.sunlinh@gmail.com";

    description "This model defines a YANG data model that can be 
    used to configure and manage Kea DHCPv6 server.";

    revision 2016-07-16 {
        description "version00: the minimum mapping between Kea 
        configuration and dhcpv6 YANG model.";

        reference "sysrepo.org";

    }

/*
 * Typedef
 */
 
    typedef duidtype {
        type union {
            type uint16;
            type string {
                pattern '(([0-9a-fA-F]{2}){2,128})';    
            }
        }
        description "the type defined for duid";
    }

/*
 * Data Nodes
 */

    container server {
        description "Kea dhcpv6 server configuration";
        container serv-attributes {
            description "gloabl attributes";
            leaf name {
                type string;
                description "server's name";
            }
            leaf duid {
                type duidtype;
                description "DHCP Unique Identifer";
            }
            leaf enable {
                type boolean;
                description "whether to enable the server";
            }
	    container lease-database {
	    	leaf type {
		    type string;
		    description "defines database type. Supported
		    		values are: memfile, mysql, pgsql,
				cassandra";
		}
		description "Defines database connection";
	    }
	    container control-socket {
                leaf socket-type {
		     type string;
		     /* @todo: change this to enum */
		     description "Type of control socket used
		     to send commands to Kea";
		}
		leaf socket-name {
		     type string;
		     description "Specifies location of the
		     unix socket Kea uses to receive commands";
		}
		description "Defines control API socket";
            }
            container interfaces-config {
                description "A leaf list to denote which one or 
                more interfaces the server should listen on. The 
                default value is to listen on all the interfaces. 
                This node is also used to set a unicast address 
                for the server to listen with a specific interface. 
                For example, if people want the server to listen 
                on a unicast address with a specific interface, he 
                can use the format like 'eth1/2001:db8::1'.";
                leaf-list interfaces {
                    type string;
                    description "the specific interfaces";
                }
            }
            leaf description {
                type string;
                description "description of the server";
            }
            leaf stateless-service {
                type boolean;
                description "A boolean value specifies whether 
                the server support client-server exchanges 
                involving two messages defined in ([RFC3315]).";
            }
            leaf renew-timer {
                type yang:timeticks;
                description "renew time in seconds";
            }
            leaf rebind-timer {
                type yang:timeticks;
                description "rebind time in seconds";
            }
            leaf preferred-lifetime {
                type yang:timeticks;
                description "preferred lifetime IA in seconds";
            }
            leaf valid-lifetime {
                type yang:timeticks;
                description "valid liftime for IA";
            }
        }
        container custom-options {
            description "container for defining custom 
            DHCPv6 options";
            list custon-option{
                key option-code;
                description "container for defining custom 
                DHCPv6 options";
                leaf option-code {
                    type uint16;
                    description "option code for custom option";
                }
                leaf option-name {
                    type string;
                    description "option name for custom option";
                }
                leaf option-type {
                    type string;
                    description "option type for custom option";
                }
                
            }
        }
        container option-sets {
            description "option sets configruation";
            list option-set {
                key option-set-id;
                description "a specific option set";
                leaf option-set-id {
                    type uint8; 
                    description "identifier for specific option 
                    set";   
                }
                leaf description{
                    type string;
                    description "description for the option set";
                }
                list standard-option {
                    key option-code;
                    description "standard format for DHCPv6 
                    option";
                    leaf option-code {
                        type uint16;
                        description "option code for standard option";
                    }
                    leaf option-name {
                        type string;
                        description "option name for standard option";
                    }
                    leaf option-value {
                        type string;
                        description "option data for standard option";
                    }
                    leaf csv-format {
                        type boolean;
                        description "whether csv-format is employed";
                    }
                }
            }
        }
        container network-ranges {
            description "gloabl level for DHCPv6 server";
            leaf option-set-id {
                type uint8;
                description "selected option set for global level";
            }
            leaf rapid-commit {
                type boolean;
                description "whether rapid commit is enabled 
                gloablly";
            }
            list subnet6 {
                key subnet;
                description "A subnet of DHCPv6 server";
                leaf network-range-id {
                    type uint8;
                    description "subnet id";
                }
                leaf network-description {
                    type string;
                    description "description for the subnet";
                }
                leaf subnet {
                    type inet:ipv6-prefix;
                    description "the subnet prefix";
                }
                leaf option-set-id {
                    type uint8;
                    description "selected option set for this 
                    subnet";
                }
                leaf rapid-commit {
                    type boolean;
                    description "whether rapid commit is enabled 
                    for this subnet";
                }
                leaf interface {
                    type string;
                    description "IPv6 subnet selction";
                }
                leaf interface-id {
                    type string;
                    description "content of the interface-id 
                    option used by relays";
                }
                leaf relay-address {
                    type inet:ipv6-address;
                    description "specify which relay will be 
                    used";
                }
                container pools {
                    description "address pools for this subnet";
                    list address-pool {
                        key pool-id;
                        description "a specific address pool";
                        leaf pool-id {
                            type uint8;
                            description "address pool 
                            indentifier";
                        }
                        leaf pool-prefix {
                            type inet:ipv6-prefix;
                            description "the pool prefix";
                        }
                        leaf start-address {
                            type inet:ipv6-address;
                            description "start address";
                        }
                        leaf end-address {
                            type inet:ipv6-address;
                            description "end address";
                        }
                    }
                }
                container prefix-pools {
                    description "prefix pools for this subnet";
                    list prefix-pool {
                        key pool-id;
                        description "a specific prefix pool";
                        leaf pool-id {
                            type uint8;
                            description "prefix pool 
                            indentifier";
                        }
                        leaf pool-prefix {
                            type inet:ipv6-prefix;
                            description "available prefix";
                        }
                    }
                }
                list reserved-host {
                    key cli-id;
                    description "host reservation";
                    leaf cli-id {
                        type uint32;
                        description "a cli-id is corresponding 
                        to a specific host (DUID)";
                    }
                    leaf duid {
                        type duidtype;
                        description "host's DUID";
                    }
                    leaf hardware-addr {
                        type yang:mac-address;
                        description "host's mac address";
                    }
                    leaf-list reserv-addr {
                        type inet:ipv6-address;
                        description "reserved IPv6 addresses";
                    }
                }
            }
        }
        container rsoo-enabled-options {
            description "rsoo enabled options";
            list rsoo-enabled-option{
                key option-code;
                description "rsoo enabled option";
                leaf option-code {
                    type uint16;
                    description "option code";
                }
                leaf description {
                    type string;
                    description "description of the option";
                }                    
            }
        }
    }
}
